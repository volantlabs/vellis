package VellisModel {
    /* Convenience package exposing the complete current model. */

    public import VellisFoundation::*;
    public import RTGDomain::*;
    public import VellisServiceContracts::*;
    public import VellisSystems::*;
    public import RTGUseCases::*;
    public import VellisUseCases::*;
    public import VellisRequirements::*;
    public import VellisContexts::*;
}
